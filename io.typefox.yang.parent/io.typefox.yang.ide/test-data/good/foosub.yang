submodule foosub {
    yang-version 1.1;
    belongs-to foo {
        prefix "fooprefix";
    }
    grouping mygrouping {
        container c12 {
        }
    }
    uses "fooprefix:mygrouping" {
        augment "c12" {
            container augmented {}
        }
    }
}
