module xpath-serialize {
    namespace xpath;
    prefix xs;
    yang-version 1.1;
    import yangster-test {
        prefix ytest;
    }
    container cb {
        must "number(.) <= number(lb/list-leaf-"
        +"c/leafref)";

        list lb {
            leaf lfb {
                type leafref {
                    path "/ytest:c1/ytest:l1";
                }
            }
            leaf lfb2 {
                type leafref {
                    path "/ytest:c1" + "/ytest:l1";
                }
            }
            leaf lfb3 {
                type leafref {
                    path "/ytest:c1/" + "ytest:l1";
                }
            }
            leaf lfb4 {
                type leafref {
                    path "/ytest:" + "c1/ytest" + ":l1";
                }
            }
            leaf list-leaf-c {
                type leafref {
                    path "/ytest:cont-one/ytest:leaf-one";
                }
            }
            leaf list-leaf-c2 {
                type leafref {
                    path "/ytest:cont-" + "one/ytest:leaf" + "-one";
                }
            }
            leaf list-leaf-c3 {
                type leafref {
                    path "/ytest:cont-" + "one/ytest:" + "leaf" + "-one";
                }
            }
        }
    }
}
