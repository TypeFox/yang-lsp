// Generated by EYangPreprocessorUtil (1.14.0-5 2019-12-09 16:57:14 CET) on Feb 14, 2020 11:33:03 AM
module _3gpp-common-managed-function {
    yang-version 1.1;
    namespace urn:3gpp:sa5:_3gpp-common-managed-function;
    prefix mf3gpp;

    revision 2019-06-18;

    grouping Function_Grp {
        leaf userLabel {
            type string;
            description
              "A user-friendly (and user assignable) name of this object.";
        }
    }

    grouping ManagedFunctionGrp {
        uses Function_Grp;

        container vnfParametersList {

            leaf vnfInstanceId {
                type string;
                mandatory true;
                description
                  "VNF instance identifier";
            }

            leaf vnfdId {
                type string;
            }

            leaf flavourId {
                type string;
            }

            leaf autoScalable {
                type boolean;
                mandatory true;
            }
        }

        container peeParametersList {

            leaf siteIdentification {
                type string;
                mandatory true;
            }

            leaf siteLatitude {
                type decimal64 {
                    fraction-digits 4;
                    range "-90.0000..+90.0000";
                }
            }

            leaf siteLongitude {
                type decimal64 {
                    fraction-digits 4;
                    range "-180.0000..+180.0000";
                }
            }

            leaf siteDescription {
                type string;
                mandatory true;
            }
        }

        leaf priorityLabel {
            mandatory true;
            type uint32;
        }
    }
}
