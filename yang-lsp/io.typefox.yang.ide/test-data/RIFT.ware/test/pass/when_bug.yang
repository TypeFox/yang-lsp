module when_bug {

  yang-version 1;

  namespace "http://www.when_bug.com/";

  prefix wbug;

  import iana-if-type {
    prefix ianaift;
  }

  organization "Augment When Bug";

  contact "augment@bug.com";

  description "Example file to find the augment bug.";

  revision "2012-06-14" {
    description "Initial revision.";
  }


  container when_bug {
    list interface {
      key "name";
      leaf name {
        type string;
      }

//      leaf type {
//        type ianaift:iana-if-type;
//        mandatory true;
//      }
    } // list interface
  } // container when_bug

  augment "/when_bug/interface" {
    when "type = 'ethernetCsmacd'";
    leaf when_b {
      type boolean;
      default 'false';
    }

    leaf when_i {
      type int32;
    }

    container cont {
      leaf eth {
        type int32;
      }
    } // container cont
  }
}
