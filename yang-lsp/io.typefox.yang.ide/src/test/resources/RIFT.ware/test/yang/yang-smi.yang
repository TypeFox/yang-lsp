module yang-smi {

    // XXX namespace to be allocated by IANA

    namespace "urn:ietf:params:xml:ns:yang:yang-smi";
    prefix "smi";

    organization
        "YANG Language Design Team";

    contact
        "Martin Bjorklund (Editor) <mail@domain.xyz>";

    description
        "This module contains extensions for dealing with 
         SMIv2 modules.";

    revision 2008-03-20 {
        description "Initial revision.";
    }

    extension oid {
        description
           "OBJECT IDENTIFIER value assigned to a particular node.";
        argument "oid";
    }

    extension display-hint {
        description
           "DISPLAY-HINT value provided in a TEXTUAL-CONVENTION macro.";
        argument "hint";
    }

    extension default {
        description
           "DEFVAL value provided in an OBJECT-TYPE macro.";
        argument "default";
    }

}
