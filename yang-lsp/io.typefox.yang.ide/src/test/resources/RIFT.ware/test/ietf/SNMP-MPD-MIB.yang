/*
 * This module has been generated by smidump 0.4.6:
 *
 *      smidump -f yang --yang-smi-extensions SNMP-MPD-MIB
 *
 * Do not edit. Edit the source file instead!
 */

module SNMP-MPD-MIB {

   /*** NAMESPACE / PREFIX DEFINITION ***/

   namespace "urn:ietf:params:xml:ns:yang:smiv2:SNMP-MPD-MIB";
   prefix "snmp-mpd";

   /*** LINKAGE (IMPORTS / INCLUDES) ***/

   import yang-smi   { prefix "smi"; }
   import ietf-yang-types { prefix "yang"; }

   /*** META INFORMATION ***/

   organization     
     "SNMPv3 Working Group";

   contact          
     "WG-EMail:   mail@domain.xyz
      Subscribe:  mail@domain.xyz
      
      Co-Chair:   Russ Mundy
                  Network Associates Laboratories
      postal:     15204 Omega Drive, Suite 300
                  Rockville, MD 20850-4601
                  USA
      
      EMail:      mail@domain.xyz
      phone:      +1 301-947-7107
      
      Co-Chair &
      Co-editor:  David Harrington
                  Enterasys Networks
      postal:     35 Industrial Way
                  P. O. Box 5005
                  Rochester NH 03866-5005
                  USA
      EMail:      mail@domain.xyz
      phone:      +1 603-337-2614
      
      Co-editor:  Jeffrey Case
                  SNMP Research, Inc.
      postal:     3001 Kimberlin Heights Road
                  Knoxville, TN 37920-9716
                  USA
      EMail:      mail@domain.xyz
      phone:      +1 423-573-1434
      
      Co-editor:  Randy Presuhn
                  BMC Software, Inc.
      postal:     2141 North First Street
                  San Jose, CA 95131
                  USA
      EMail:      mail@domain.xyz
      phone:      +1 408-546-1006
      
      Co-editor:  Bert Wijnen
                  Lucent Technologies
      postal:     Schagen 33
                  3461 GL Linschoten
                  Netherlands
      EMail:      mail@domain.xyz
      phone:      +31 348-680-485";

   description      
     "The MIB for Message Processing and Dispatching
      
      Copyright (C) The Internet Society (2002). This
      version of this MIB module is part of RFC 3412;
      see the RFC itself for full legal notices.";

   revision "2002-10-14" {
      description   
        "Updated addresses, published as RFC 3412.";
   }
   revision "1999-05-04" {
      description   
        "Updated addresses, published as RFC 2572.";
   }
   revision "1997-09-30" {
      description   
        "Original version, published as RFC 2272.";
   }

   container snmpMPDStats {

      leaf snmpUnknownSecurityModels {
         type yang:counter32;
         config false;
         description 
           "The total number of packets received by the SNMP
            engine which were dropped because they referenced a
            securityModel that was not known to or supported by
            the SNMP engine.";
         smi:oid "1.3.6.1.6.3.11.2.1.1";
      }

      leaf snmpInvalidMsgs {
         type yang:counter32;
         config false;
         description 
           "The total number of packets received by the SNMP
            engine which were dropped because there were invalid
            or inconsistent components in the SNMP message.";
         smi:oid "1.3.6.1.6.3.11.2.1.2";
      }

      leaf snmpUnknownPDUHandlers {
         type yang:counter32;
         config false;
         description 
           "The total number of packets received by the SNMP
            engine which were dropped because the PDU contained
            in the packet could not be passed to an application
            responsible for handling the pduType, e.g. no SNMP
            application had registered for the proper
            combination of the contextEngineID and the pduType.";
         smi:oid "1.3.6.1.6.3.11.2.1.3";
      }
      smi:oid "1.3.6.1.6.3.11.2.1";
   }

} /* end of module SNMP-MPD-MIB */
