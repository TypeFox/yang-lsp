module ietf-snmp {

  namespace "urn:ietf:params:xml:ns:yang:ietf-snmp";
  prefix snmp;

  include ietf-snmp-common {
    revision-date 2012-06-05;
  }
  include ietf-snmp-engine {
    revision-date 2012-06-05;
  }
  include ietf-snmp-target {
    revision-date 2012-06-05;
  }
  include ietf-snmp-notification {
    revision-date 2012-06-05;
  }
  include ietf-snmp-proxy {
    revision-date 2012-06-05;
  }
  include ietf-snmp-community {
    revision-date 2012-06-05;
  }
  include ietf-snmp-usm {
    revision-date 2012-06-05;
  }
  include ietf-snmp-tsm {
    revision-date 2012-06-05;
  }
  include ietf-snmp-vacm {
    revision-date 2012-06-05;
  }
  include ietf-snmp-tls {
    revision-date 2012-06-05;
  }

  organization
    "IETF NETMOD (NETCONF Data Modeling Language) Working Group";

  contact
    "WG Web:   <http://tools.ietf.org/wg/netmod/>
     WG List:  <mailto:mail@domain.xyz>
     WG Chair: John Smith
               <mailto:mail@domain.xyz>

     WG Chair: John Smith
               <mailto:mail@domain.xyz>

     Editor:   Martin Bjorklund
               <mailto:mail@domain.xyz>

     Editor:   John Smith
               <mailto:mail@domain.xyz>";

  description
    "This module contains a collection of YANG definitions for
     configuring SNMP engines.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: update the date below with the date of RFC publication
  // and remove this note.

  revision 2012-06-05 {
    description
      "Initial revision.";
    reference
      "RFC XXXX: A YANG Data Model for SNMP Configuration";
  }

}
