/*
 * This module has been generated by smidump 0.4.6:
 *
 *      smidump -f yang --yang-smi-extensions DIFFSERV-DSCP-TC
 *
 * Do not edit. Edit the source file instead!
 */

module DIFFSERV-DSCP-TC {

   /*** NAMESPACE / PREFIX DEFINITION ***/

   namespace "urn:ietf:params:xml:ns:yang:smiv2:DIFFSERV-DSCP-TC";
   prefix "diffserv-dscp";

   /*** LINKAGE (IMPORTS / INCLUDES) ***/

   import yang-smi { prefix "smi"; }

   /*** META INFORMATION ***/

   organization     
     "IETF Differentiated Services WG";

   contact          
     "       Fred Baker
      Cisco Systems
      1121 Via Del Rey
      Santa Barbara, CA 93117, USA
      E-mail: mail@domain.xyz
      
      Kwok Ho Chan
      Nortel Networks
      600 Technology Park Drive
      Billerica, MA 01821, USA
      E-mail: mail@domain.xyz
      
      Andrew Smith
      Harbour Networks
      Jiuling Building
      21 North Xisanhuan Ave.
      Beijing, 100089, PRC
      E-mail: mail@domain.xyz
      
        Differentiated Services Working Group:
        mail@domain.xyz";

   description      
     "The Textual Conventions defined in this module should be used
      whenever a Differentiated Services Code Point is used in a MIB.";

   revision "2002-05-09" {
      description   
        "Initial version, published as RFC 3289.";
   }

   /*** TYPE DEFINITIONS ***/

   typedef Dscp {
      type int32 {
         range "0..63";
      }
      description   
        "A Differentiated Services Code-Point that may be used for
         marking a traffic stream.";
      reference     
        "RFC 2474, RFC 2780";
      smi:display-hint "d";
   }

   typedef DscpOrAny {
      type int32 {
         range "-1..63";
      }
      description   
        "The IP header Differentiated Services Code-Point that may be
         
         
         
         used for discriminating among traffic streams. The value -1 is
         used to indicate a wild card i.e. any value.";
      reference     
        "RFC 2474, RFC 2780";
      smi:display-hint "d";
   }

} /* end of module DIFFSERV-DSCP-TC */
