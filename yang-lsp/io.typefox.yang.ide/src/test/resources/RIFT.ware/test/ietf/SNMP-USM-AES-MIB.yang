/*
 * This module has been generated by smidump 0.4.6:
 *
 *      smidump -f yang --yang-smi-extensions SNMP-USM-AES-MIB
 *
 * Do not edit. Edit the source file instead!
 */

module SNMP-USM-AES-MIB {

   /*** NAMESPACE / PREFIX DEFINITION ***/

   namespace "urn:ietf:params:xml:ns:yang:smiv2:SNMP-USM-AES-MIB";
   prefix "snmp-usm";

   /*** LINKAGE (IMPORTS / INCLUDES) ***/

   import SNMP-FRAMEWORK-MIB { prefix "snmp-framework"; }
   import yang-smi           { prefix "smi"; }

   /*** META INFORMATION ***/

   organization     
     "IETF";

   contact          
     "Uri Blumenthal
      Lucent Technologies / Bell Labs
      67 Whippany Rd.
      14D-318
      Whippany, NJ  07981, USA
      973-386-2163
      mail@domain.xyz
      
      Fabio Maino
      Andiamo Systems, Inc.
      375 East Tasman Drive
      San Jose, CA  95134, USA
      408-853-7530
      mail@domain.xyz
      
      Keith McCloghrie
      Cisco Systems, Inc.
      170 West Tasman Drive
      San Jose, CA  95134-1706, USA
      
      408-526-5260
      mail@domain.xyz";

   description      
     "Definitions of Object Identities needed for
      the use of AES by SNMP's User-based Security
      Model.
      
      Copyright (C) The Internet Society (2004).
      
      This version of this MIB module is part of RFC 3826;
      see the RFC itself for full legal notices.
      Supplementary information may be available on
      http://www.ietf.org/copyrights/ianamib.html.";

   revision "2004-06-14" {
      description   
        "Initial version, published as RFC3826";
   }

} /* end of module SNMP-USM-AES-MIB */
