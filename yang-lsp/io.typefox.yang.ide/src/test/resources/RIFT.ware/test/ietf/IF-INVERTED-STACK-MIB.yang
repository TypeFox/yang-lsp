/*
 * This module has been generated by smidump 0.4.6:
 *
 *      smidump -f yang --yang-smi-extensions IF-INVERTED-STACK-MIB
 *
 * Do not edit. Edit the source file instead!
 */

module IF-INVERTED-STACK-MIB {

   /*** NAMESPACE / PREFIX DEFINITION ***/

   namespace "urn:ietf:params:xml:ns:yang:smiv2:IF-INVERTED-STACK-MIB";
   prefix "if-inverted";

   /*** LINKAGE (IMPORTS / INCLUDES) ***/

   import IF-MIB    { prefix "if-mib"; }
   import SNMPv2-TC { prefix "smiv2"; }
   import yang-smi  { prefix "smi"; }

   /*** META INFORMATION ***/

   organization     
     "IETF Interfaces MIB Working Group";

   contact          
     "   Keith McCloghrie
      Cisco Systems, Inc.
      170 West Tasman Drive
      San Jose, CA  95134-1706
      US
      
      408-526-5260
      mail@domain.xyz";

   description      
     "The MIB module which provides the Inverted Stack Table for
      interface sub-layers.";

   revision "2000-06-14" {
      description   
        "Initial revision, published as RFC 2864";
   }

   container ifInvMIBObjects {


      /* XXX table comments here XXX */

      list ifInvStackEntry {

         key "ifStackLowerLayer ifStackHigherLayer";
         description 
           "Information on a particular relationship between two sub-
            layers, specifying that one sub-layer runs underneath the
            other sub-layer.  Each sub-layer corresponds to a conceptual
            row in the ifTable.";
         smi:oid "1.3.6.1.2.1.77.1.1.1";

         leaf ifStackLowerLayer {
            type leafref {
               path "/if-mib:ifMIBObjects/if-mib:ifStackEntry/if-mib:ifStackLowerLayer";
            }
            config true;
            description   
              "Automagically generated leafref leaf.";
         }
         leaf ifStackHigherLayer {
            type leafref {
               path "/if-mib:ifMIBObjects/if-mib:ifStackEntry/if-mib:ifStackHigherLayer";
            }
            config true;
            description   
              "Automagically generated leafref leaf.";
         }

         leaf ifInvStackStatus {
            type smiv2:RowStatus;
            config false;
            description   
              "The status of the relationship between two sub-layers.
               
               An instance of this object exists for each instance of the
               ifStackStatus object, and vice versa.  For example, if the
               variable ifStackStatus.H.L exists, then the variable
               ifInvStackStatus.L.H must also exist, and vice versa.  In
               addition, the two variables always have the same value.
               
               However, unlike ifStackStatus, the ifInvStackStatus object
               is NOT write-able.  A network management application wishing
               to change a relationship between sub-layers H and L cannot
               do so by modifying the value of ifInvStackStatus.L.H, but
               must instead modify the value of ifStackStatus.H.L.  After
               the ifStackTable is modified, the change will be reflected
               in this table.";
            smi:oid "1.3.6.1.2.1.77.1.1.1.1";
         }
      }

      smi:oid "1.3.6.1.2.1.77.1";
   }

} /* end of module IF-INVERTED-STACK-MIB */
