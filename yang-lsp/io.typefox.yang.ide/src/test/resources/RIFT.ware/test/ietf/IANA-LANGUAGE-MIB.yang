/*
 * This module has been generated by smidump 0.4.6:
 *
 *      smidump -f yang --yang-smi-extensions IANA-LANGUAGE-MIB
 *
 * Do not edit. Edit the source file instead!
 */

module IANA-LANGUAGE-MIB {

   /*** NAMESPACE / PREFIX DEFINITION ***/

   namespace "urn:ietf:params:xml:ns:yang:smiv2:IANA-LANGUAGE-MIB";
   prefix "iana-language";

   /*** LINKAGE (IMPORTS / INCLUDES) ***/

   import yang-smi { prefix "smi"; }

   /*** META INFORMATION ***/

   organization     
     "IANA";

   contact          
     "Internet Assigned Numbers Authority (IANA)
      
      Postal: ICANN
              4676 Admiralty Way, Suite 330
              Marina del Rey, CA 90292
      
      Tel:    +1 310 823 9358 x20
      E-Mail: mail@domain.xyz";

   description      
     "The MIB module registers object identifier values for
      well-known programming and scripting languages. Every
      language registration MUST describe the format used
      when transferring scripts written in this language.
      
      Any additions or changes to the contents of this MIB
      module require Designated Expert Review as defined in
      the Guidelines for Writing IANA Considerations Section
      document. The Designated Expert will be selected by
      the IESG Area Director of the OPS Area.
      
      Note, this module does not have to register all possible
      languages since languages are identified by object
      identifier values. It is therefore possible to registered 
      languages in private OID trees. The references given below are not
      normative with regard to the language version. Other
      references might be better suited to describe some newer 
      versions of this language. The references are only
      provided as `a pointer into the right direction'.";

   revision "2000-05-10" {
      description   
        "Import mib-2 instead of experimental, so that
         this module compiles";
   }
   revision "1999-09-09" {
      description   
        "Initial version as published at time of
         publication of RFC 2591.";
   }

} /* end of module IANA-LANGUAGE-MIB */
