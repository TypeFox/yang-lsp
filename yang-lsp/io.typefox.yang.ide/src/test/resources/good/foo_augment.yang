module foo_augment {
	yang-version 1.1;
    namespace "http://www.dfefge.rf/dsfdf/sdf";
    prefix "aug";
    import foo {
        prefix "foo";
    }

    augment "/foo:c12/foo:cool" {
        container augmented {}
    }
}
