module yang-dep {
    yang-version 1.1;
    namespace "http://yangster.org";
    prefix ydep;

    extension e1 {
    }

    rpc aio {
       description  "action";
       input {
           leaf key {
               type string;
           }
       }
       output {
           leaf value {
              type string;
           }
       }
    }

    rpc ai {
       description  "action";
       input {
           leaf key {
               type string;
           }
       }
    }

}
